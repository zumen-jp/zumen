;; zumen の公開サンプル（samples/dwg）を作る（#316）。make.sh が、画面なしの accoreconsole で主題ごとに 1 つの図面を作り、
;; バージョンごとに DWG と DXF（_ascii.dxf）に保存する
(setq zs-out "C:/zumen-work/out/")
(defun zs-begin () (setvar "CMDECHO" 1) (setvar "INSUNITS" 4) (setvar "ATTREQ" 0) (setvar "OSMODE" 0))
(defun zs-save (name vers)
  (command "_.ZOOM" "_E")
  (repeat 3 (command "_.-PURGE" "_A" "*" "_N"))
  (command "_.-PURGE" "_R" "*" "_N")
  (foreach v vers
    (command "_.SAVEAS" v (strcat zs-out "zumen-" name "-r" v ".dwg"))
    (command "_.DXFOUT" (strcat zs-out "zumen-" name "-r" v "_ascii.dxf") "_V" v "16")))
(defun zs-arc (c r a1 a2)
  (command "_.ARC" "_C" c (polar c (* pi (/ a1 180.0)) r) "_A" (rtos (- a2 a1) 2 6))
  (entlast))
(defun zs-mid (c r a1 a2) (polar c (* pi (/ (+ a1 a2) 360.0)) r))

;; 1. 弧長寸法: 記号の位置 3 通り、部分、引出線、寸法値の上書き
(defun zs-arcdim (/ e c)
  (zs-begin)
  (foreach s '((0 0) (1 150) (2 300))
    (setvar "DIMARCSYM" (car s))
    (setq c (list (cadr s) 0.0 0.0) e (zs-arc c 50.0 30.0 120.0))
    (command "_.DIMARC" (list e (zs-mid c 50.0 30.0 120.0)) (polar c (* pi (/ 75.0 180)) 65.0)))
  (setvar "DIMARCSYM" 0)
  (setq c '(0.0 -150.0 0.0) e (zs-arc c 40.0 0.0 180.0))
  (command "_.DIMARC" (list e (zs-mid c 40.0 0.0 180.0)) "_P" (polar c (* pi (/ 30.0 180)) 40.0) (polar c (* pi (/ 60.0 180)) 40.0) (polar c (* pi (/ 45.0 180)) 55.0))
  (setq c '(150.0 -150.0 0.0) e (zs-arc c 40.0 0.0 150.0))
  (command "_.DIMARC" (list e (zs-mid c 40.0 0.0 150.0)) "_L" (polar c (* pi (/ 45.0 180)) 60.0) "")
  (setq c '(300.0 -150.0 0.0) e (zs-arc c 40.0 0.0 90.0))
  (command "_.DIMARC" (list e (zs-mid c 40.0 0.0 90.0)) "_T" "上書き<>" (polar c (* pi (/ 45.0 180)) 55.0))
  (zs-save "arcdim" '("2004" "2018")))

;; 4. ブロックの切り抜き: 長方形、多角形、反転。ブロックは回転と尺度つき
(defun zs-xclip (/ ss i)
  (zs-begin)
  (setvar "XCLIPFRAME" 1)
  (command "_.LINE" "0,0" "40,0" "40,20" "0,20" "_C")
  (setq ss (ssget "_X"))
  (command "_.CIRCLE" "20,10" "8") (ssadd (entlast) ss)
  (command "_.LINE" "0,0" "40,20" "") (ssadd (entlast) ss)
  (command "_.-BLOCK" "CLIPPED" "0,0" ss "")
  (command "_.INSERT" "CLIPPED" "0,0" "2" "2" "30")
  (command "_.XCLIP" (entlast) "" "_N" "_R" "10,10" "50,40")
  (command "_.INSERT" "CLIPPED" "150,0" "2" "2" "0")
  (command "_.XCLIP" (entlast) "" "_N" "_P" "160,5" "200,5" "220,35" "170,35" "")
  (command "_.INSERT" "CLIPPED" "300,0" "2" "2" "0")
  (command "_.XCLIP" (entlast) "" "_N" "_I" "_R" "320,10" "360,30")
  (zs-save "xclip" '("2013" "2018")))

;; 5. レイアウト: A3 の 1:1、A3 の 1:2、インチの用紙。ビューポートは 1:50 と 1:100
(defun zs-setup (layout paper units scale)
  (setvar "CTAB" layout)
  (command "_.-PAGESETUP" "Microsoft Print to PDF" paper units "_L" "_N" "_L" scale "0,0" "_Y" "." "_Y" "_N" "_N" "_N"))
(defun zs-vport (p1 p2 xp / v)
  (command "_.MVIEW" p1 p2)
  (setq v (entlast))
  (command "_.MSPACE")
  (setvar "CVPORT" (cdr (assoc 69 (entget v))))
  (command "_.ZOOM" "_C" "100,50" xp)
  (command "_.PSPACE"))
(defun zs-layout ()
  (zs-begin)
  (command "_.RECTANG" "0,0" "200,100")
  (command "_.CIRCLE" "100,50" "30")
  (command "_.-LAYOUT" "_N" "A3-1to1")
  (command "_.-LAYOUT" "_N" "A3-1to2")
  (command "_.-LAYOUT" "_N" "Letter-inch")
  (zs-setup "A3-1to1" "A3" "_M" "1:1")
  (zs-vport "20,20" "200,150" "1/50xp")
  (zs-vport "220,20" "400,150" "1/100xp")
  (zs-setup "A3-1to2" "A3" "_M" "1:2")
  (zs-vport "20,20" "400,280" "1/50xp")
  (zs-setup "Letter-inch" "Letter" "_I" "1:1")
  (zs-vport "1,1" "10,7" "1/2000xp")
  (setvar "CTAB" "Model")
  (zs-save "layout" '("2000" "2004" "2018")))

;; 6. MINSERT: 属性なしと属性つき、回転と尺度を変える
(defun zs-minsert (/ ss)
  (zs-begin)
  (command "_.RECTANG" "0,0" "8,4")
  (setq ss (ssadd (entlast)))
  (command "_.-BLOCK" "CELL" "0,0" ss "")
  (command "_.RECTANG" "0,0" "8,4")
  (setq ss (ssadd (entlast)))
  (command "_.-ATTDEF" "" "NO" "番号" "A1" "1,1" "2" "0")
  (ssadd (entlast) ss)
  (command "_.-ATTDEF" "" "KIND" "種類" "壁" "1,2.5" "1" "0")
  (ssadd (entlast) ss)
  (command "_.-BLOCK" "TAGGED" "0,0" ss "")
  (command "_.MINSERT" "CELL" "0,0" "1" "1" "0" "2" "3" "10" "20")
  (command "_.MINSERT" "CELL" "100,0" "2" "1.5" "30" "3" "2" "15" "25")
  (command "_.MINSERT" "TAGGED" "0,100" "1" "1" "0" "2" "3" "10" "20")
  (command "_.MINSERT" "TAGGED" "100,100" "1.5" "1.5" "15" "2" "2" "12" "30")
  (zs-save "minsert" '("2000" "2004" "2018")))

;; 8. 点: 0 番レイヤ、印刷しないレイヤ、Defpoints、BYBLOCK のブロック
(defun zs-points (mode size name / ss)
  (zs-begin)
  (setvar "PDMODE" mode)
  (setvar "PDSIZE" size)
  (command "_.-LAYER" "_N" "NOPLOT" "_P" "_N" "NOPLOT" "")
  (command "_.-LAYER" "_N" "Defpoints" "")
  (command "_.POINT" "0,0")
  (command "_.-LAYER" "_S" "NOPLOT" "") (command "_.POINT" "20,0")
  (command "_.-LAYER" "_S" "Defpoints" "") (command "_.POINT" "40,0")
  (command "_.-LAYER" "_S" "0" "")
  (command "_.POINT" "0,0") (setq ss (ssadd (entlast)))
  (command "_.CHPROP" ss "" "_C" "BYBLOCK" "_LT" "BYBLOCK" "")
  (command "_.LINE" "-5,-5" "5,5" "") (ssadd (entlast) ss)
  (command "_.CHPROP" (entlast) "" "_C" "BYBLOCK" "_LT" "BYBLOCK" "")
  (command "_.-BLOCK" "BYBLOCKPOINT" "0,0" ss "")
  (command "_.INSERT" "BYBLOCKPOINT" "60,0" "1" "1" "0")
  (command "_.-LAYOUT" "_N" "Sheet")
  (setvar "CTAB" "Sheet")
  (command "_.POINT" "10,10")
  (setvar "CTAB" "Model")
  (zs-save name '("2000" "2018")))
(princ)
